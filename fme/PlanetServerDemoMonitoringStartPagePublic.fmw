FME workspace PlanetServerDemoMonitoringStartPagePublic.fmw

Writers:
- HTML_1: HTML to C:\Temp\monitoringStartPage.htm

Note: Prepare the html wtith two calender widgets and the last image read directly from S3
AttributeCreator_2
    ATTR_TABLE:
      SET_TO html_content = <html xmlns="http://www.w3.org/1999/xhtml" xml:lang="en">
        <head>
        <title>Farm land monitoring</title>

        	<style type="text/css">

         	 h1,p {
        		 	font-family: Arial, Helvetica, sans-serif;
        		}
           table {
            margin-left:auto;
            margin-right:auto;
            table-layout:fixed;
            width: 50%
           }

           html, body {
            height: 100%;
            margin: 5px;
            padding: 0;
           }

           img {
            padding: 0;
            display: block;
            margin: 0 auto;

           }

        	</style>

            <script>
              function GetAnalysisPage(){

                var fromDate = document.getElementById("myDate1").value.replace(/-/g,"");
                var toDate   = document.getElementById("myDate2").value.replace(/-/g,"");
                var monitoring_url = "https://bluesky-safe-software.fmecloud.com/fmedatastreaming/Dmitri/PlanetServerDemoMonitoring.fmw?FROMDATE="+fromDate+"&TODATE="+toDate
                window.open(monitoring_url);
        	      }

            </script>
         </head>
         <body>
          <table>
           <tr>
            <td>
             <h1>Farmland Monitoring with Planet Imagery and FME Cloud</h1>
             <p>This demo shows how to collect, transform, and compare <a href="http://www.planet.com">Planet imagery</a> over a certain
                   area. The demo consists of three workspaces. One workspace checks and downloads new Planet images as soon as they become
                   available. It produces four outputs - RGB thumbnails, full resolution RGB, NIr (Near Infrared ), and NDVI (Normalized Difference Vegetation Index).</p>
              <p>The second workspace displays this page - it shows the latest image and allows selecting the date range for visualization.</p>
              <p>The third workspace shows the previews of all available images within the given range and allows comparing two selected images
                   in any of three representations - RGB, NIr, and NDVI.</p>
             <p>Select time frame for visualization and press "Submit" button.</p>
             <form>
              <input type="date" id="myDate1" value="2016-01-01">
              <input type="date" id="myDate2" value="@DateTimeFormat(@DateTimeNow(),%Y-%m-%d)">
              <input type="submit" id="submitDate" onclick="GetAnalysisPage()" value="Submit">
             </form>
             <p>The latest image for the area. Updated on @DateTimeFormat(@Value(_rootname), %Y-%m-%d)</p>
            </td>
           </tr>
           <tr>
            <td>
             <img src="https://s3-us-west-2.amazonaws.com/safe-scenarios/Planet/monitoring/RGB/@Value(_filename)"" height="60%">
            </td>
           </tr>
          </table>
         </body>
        </html>
    -> AttributeCreator_2_OUTPUT [off]
    -> HTML (writer HTML_1)
AttributeCreator_2_OUTPUT: Junction
    -> FeatureWriter [HTML]
    -> S3Uploader_2
Note: Save (or stream) as HTML
HTML (writer HTML_1)
    attributes: html_content buffer

Bookmark: Get the name of the last RGB image
Creator
    GEOMTYPE = Geometry Object
    NUM = 1
    CREATED -> S3ObjectLister
Note: List all the objects in RGB folder
S3ObjectLister
    S3_AWS_REGION = US West, Oregon (us-west-2)
    S3_TARGET_ATTRIBUTE = _s3_object_key
    S3_INCLUDE_SUBFOLDERS = No
    S3_BUCKET_NAME = <your-bucket>
    S3_OBJECT_KEY = Planet/monitoring/RGB/
    S3_OBJECT_TYPE = Folder
    S3_KEY_COUNT_ATTRIBUTE = _s3_object_key_count
    -> FilenamePartExtractor
Note: extract the file names / (which represent dates / when the images were taken)
FilenamePartExtractor
    ROOTNAME_ATTR = _rootname
    DIRPATH_ATTR = _dirpath
    FULLNAME_ATTR = _filename
    SRC_ATTR = @Value(_s3_object_key)
    EXTENSION_ATTR = _extension
    DIRNAME_ATTR = _dirname
    -> Sorter_2
Note: sort descendingly to get the last image first
Sorter_2
    SORT_PARM = _rootname NUMERIC DESCENDING
    SORTED -> Sampler
Note: keep only the last image for use on HTML page
Sampler
    SAMPLE_TYPE_LONG = First N Features
    RATE = 1
    SAMPLE_MODE = No
    SAMPLED -> AttributeCreator_2

Bookmark: Make a local file and open it
FeatureWriter
    DATASET_ATTR = _dataset
    DATASET = C:\temp
    FORMAT = HTML
    TOTAL_FEATURES_WRITTEN_ATTR = _total_features_written
    FEATURE_TYPE_LIST_ATTR = _feature_type
    SUMMARY -> StringReplacer
StringReplacer
    CASE = NO
    SRC_ATTRS = _dataset
    NO_MATCH = _FME_NO_OP_
    REGEXP = NO
    REPLACE_TEXT = \
    FIND_TEXT = /
    -> SystemCaller
SystemCaller
    CMD = "explorer "@Value(_dataset)""
    -> SystemCaller_Output
SystemCaller_Output: Logger
    MESSAGE = Feature is:
    MAXCOORDS = 0
    MAXFEATS = 0

Bookmark: Make a static S3 page
S3Uploader_2
    S3_FILE_OR_DATA = Attribute or Expression
    S3_AWS_REGION = US East, N. Virginia (us-east-1)
    S3_OBJECT_KEY = Planet/monitoring/monitoring.htm
    S3_UPLOAD_ENCRYPTION = None
    S3_BUCKET_NAME = <your-bucket>
    S3_DATA = @Value(html_content)
    S3_URI_ATTRIBUTE = _s3_object_uri
    S3_CANNED_ACL = Public Read
    S3_CUSTOM_HEADERS = Content-Type;text/html
    S3_ACCELERATION = No
