FME workspace PlanetServerDemoMonitoringPublic.fmw

Parameters:
- FROMDATE = 20170201   # "{}" From
- TODATE = 20170604   # "{}" To

Writers:
- HTML_1: HTML to C:\Temp\monitoring.htm

Note: The workspace lists all available images, finds the last one, and creates an HTML page that shows two calender widgets (for the beginning and the end of a date range) and the latest image. / The JavaScript code in HTML calls another page (workspace), that shows all available thumbnails withing the given range and allows comparing RGB/IR/NDVI representations of the data
Creator
    NUM = 1
    GEOMTYPE = Geometry Object
    CREATED -> S3ObjectLister
Note: List all the objects in RGB folder
S3ObjectLister
    S3_AWS_REGION = US West, Oregon (us-west-2)
    S3_OBJECT_TYPE = Folder
    S3_INCLUDE_SUBFOLDERS = No
    S3_BUCKET_NAME = <your-bucket>
    S3_KEY_COUNT_ATTRIBUTE = _s3_object_key_count
    S3_TARGET_ATTRIBUTE = _s3_object_key
    S3_OBJECT_KEY = Planet/monitoring/thumbnails/
    -> FilenamePartExtractor
Note: extract the file names / (which represent dates / when the images were taken)
FilenamePartExtractor
    EXTENSION_ATTR = _extension
    FULLNAME_ATTR = _filename
    SRC_ATTR = @Value(_s3_object_key)
    ROOTNAME_ATTR = _rootname
    DIRNAME_ATTR = _dirname
    DIRPATH_ATTR = _dirpath
    -> Tester
Note: Keep only images within the given date range
Tester
    TEST_MODE = Automatic
    BOOL_OP = AND
    TEST_DESCRIPTION = ""
    TEST_CLAUSE:
      TEST $(FROMDATE) <= @Value(_rootname)
      TEST $(TODATE) >= @Value(_rootname)
    PASSED -> Sorter_2
Note: sort descendingly to get the last image on top of the list, / and oldest - on the bottom
Sorter_2
    SORT_PARM = _rootname NUMERIC DESCENDING
    SORTED -> Counter_2
Note: assign a unique number starting from 0
Counter_2
    START = 0
    SCOPE = Global
    DOMAIN = counter
    CNT_ATTR = _count
    -> AttributeCreator
Note: if the number is 0, this will be the first and checked entry in the radio button groups / make html for each image 9two radio buttons)
AttributeCreator
    ATTR_TABLE:
      SET_TO _checked = FME_CONDITIONAL:DEFAULT_VALUE'_FME_NO_OP_'BOOL_OP;OR;COMPOSITE_TEST;<Unused>;TEST @Value(_count) = 0'checked'FME_NUM_CONDITIONS2___
      SET_TO _html =       <tr>
               <td><input type="radio" name="before" onclick="ReplaceImage('1','@Value(_rootname)')"  value="@Value(_rootname)" @Value(_checked)></td>
               <td><input type="radio" name="after"    onclick="ReplaceImage('2','@Value(_rootname)')"  value="@Value(_rootname)" @Value(_checked)></td>
               <td>@DateTimeFormat(@Value(_rootname),"%Y-%m-%d")</td>
               <td><img src="https://s3-us-west-2.amazonaws.com/safe-scenarios/@Value(_s3_object_key)" width="160" height="95"></td>
              </tr>
    -> Aggregator
Note: aggregate all html snippets into a single html
Aggregator
    CONCAT_ATTRS = _html
    ORDERED = No
    MODE = Attributes Only
    ACCUM_ATTRS_NAME = Use Attributes From One Feature
    AGGREGATE -> AttributeCreator_2
Note: Add the beginning and the end of HTML
AttributeCreator_2
    ATTR_TABLE:
      SET_TO html_content = <html xmlns="http://www.w3.org/1999/xhtml" xml:lang="en">
         <head>
          <title>Farm land monitoring</title>
           <style type="text/css" media="screen">
        	.beforeafter { position: relative; overflow: hidden; }
        	.before, .after { position: absolute; top: 0; left: 0; }
        	.before {
        		border-right: 1px solid #000;
        		-moz-box-shadow: 1px 0 5px #95;
        		-webkit-box-shadow: 1px 0 5px #95;
        		box-shadow: 1px 0 5px #95;
        	 }
        	.help {
        		position: absolute;
        		top: 50px;
        		left:  20px;
        		font: bold 20px/1em Helvetica, Arial, sans-serif;
        		color: #FFF;
        		opacity: 0.7;
        	 }
        	 table {
        	 	font-family: Arial, Helvetica, sans-serif;
        	 	font-size: 11px;
        	 }
             div.container {
                width: 100%;
                height: 100%;
             }
             div.imagery {
                margin-left:310px;
                overflow:hidden;
                height: 100%;
             }
            div.previews {
                width:300px;
        		overflow-y:scroll;
        		float:left;
                height: 100%;
         	 }
        	</style>

        <script type="text/javascript" charset="utf-8">
        /*! jQuery v3.2.1 | (c) JS Foundation and other contributors | jquery.org/license */
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

        	</script>
        	<script type="text/javascript" charset="utf-8">
        		$(function(){
        			// Loop through all the sets of before and after pics
        			$(".beforeafter").each(function(){
        				// Set the container's size to the size of the image
        				$(this).width($(this).find("img[rel=before]").attr("width")).height($(this).find("img[rel=before]").attr("height"));
        				// Convert the images into background images on layered divs
        				$(this).append("<div class='after' id='after'></div>").find(".after").css({"background": "url(" + $(this).find("img[rel=after]").attr("src") + ")", "width": $(this).find("img[rel=after]").attr("width") + "px", "height": $(this).find("img[rel=after]").attr("height") + "px"});
        				$(this).append("<div class='before' id='before'></div>").find(".before").css({"background": "url(" + $(this).find("img[rel=before]").attr("src") + ")", "width": $(this).find("img[rel=before]").attr("width") -5 + "px", "height": $(this).find("img[rel=before]").attr("height") + "px"});
        				// Add a helpful message
        				$(this).append("<div class='help'>Hover over the image to toggle before/after</div>");
        				// Remove the original images
        				$(this).find("img").remove();
        				// Event handler for the mouse moving over the image
        				$(this).mousemove(function(event){
        					// Need to know the X position of the parent as people may have their browsers set to any width
        					var offset = $(this).offset().left;
        					// Don't let the reveal go any further than 50 pixels less than the width of the image
        					// or 50 pixels on the left hand side
        					if ((event.clientX - offset) < ($(this).find(".after").width() -5) && (event.clientX - offset) > 5) {
        						// Adjust the width of the top image to match the cursor position
        						$(this).find(".before").width(event.clientX - offset);
        					}
        				});
        				// Fade out the help message after the first hover
        				$(this).hover(function(){
        					$(this).find(".help").animate({"opacity": 0}, 400, function(){ $(this).find(".help").remove(); });
        				});
        			});
        		});
        	</script>

        	<script>
            //replace images before and after with the current selection in the archive and current type
            //image_num is 1 or 2 in the image stack
        		function ReplaceImage(image_num, image_date) {

               //get the list of type choices
               var imagechoices = document.getElementsByName('image'+image_num+'type');
               var image_type;
               //create 'before' or 'after' variable for the image stack
               var image_order;
               if (image_num == 1){
                 image_order = 'before'
               }
               else {
               	 image_order = 'after'
               }
               //find what image type is checked - RGB, IR, or NDVI
               for(var i = 0; i < imagechoices.length; i++){
                 if(imagechoices[i].checked){
                      image_type  = imagechoices[i].value;
                 }
               }
               //Replace the image in the stack with the current selection - based on 'before' or 'after', date, type
               document.getElementById(image_order).style.backgroundImage = "url(https://s3-us-west-2.amazonaws.com/safe-scenarios/Planet/monitoring/".concat(image_type,"/",image_date,".png")
            }

            function ChangeType(image_type, image_order){
            	var image_dates = document.getElementsByName(image_order);
               //find what image date is checked
               var image_date
               for(var i = 0; i < image_dates.length; i++){
                 if(image_dates[i].checked){
                      image_date = image_dates[i].value;
                 }
               }

            	document.getElementById(image_order).style.backgroundImage = "url(https://s3-us-west-2.amazonaws.com/safe-scenarios/Planet/monitoring/".concat(image_type,"/",image_date,".png")
            }

        	</script>

        </head>


        <body>
        	<div class="container">
            <div class="previews">
             <table style="border: 1px solid black">
              <tr><th>1</th><th>2</th><th>Date</th><th>Preview</th></tr>
        @Value(_html)
             </table>

            </div>

            <div class="imagery">
               <p>Select dates on the left, and representation for each date below. Move the mouse over the image to compare two representations</p>
               <p>The original JavaScript code for image comparison provided by Greg Patterson (<a href="mailto:Greg.Patterson@cit.edu.au">email</a>).</p>
        	   <table>
        	  	<tr>
        	  		<th>Image 1</th>
        	  		<th>Image 2</th>
        	  	</tr>
        	  	<tr>
        	  	 <td>

        	  	  <input type="radio" name="image1type" onclick="ChangeType('RGB',  'before')" value="RGB" checked>RGB<br>
                  <input type="radio" name="image1type" onclick="ChangeType('IR',   'before')" value="IR">IR<br>
                  <input type="radio" name="image1type" onclick="ChangeType('NDVI', 'before')" value="NDVI">NDVI
                 </td>
        	  	 <td>
        	  		<input type="radio" name="image2type" onclick="ChangeType('RGB',  'after')" value="RGB" checked>RGB<br>
                    <input type="radio" name="image2type" onclick="ChangeType('IR',   'after')" value="IR">IR<br>
                    <input type="radio" name="image2type" onclick="ChangeType('NDVI', 'after')" value="NDVI">NDVI
                  </td>
                 </tr>
        	    </table>
         		<div class="beforeafter">
        		  <img src="https://s3-us-west-2.amazonaws.com/safe-scenarios/Planet/monitoring/RGB/@Value(_rootname).png" rel="before" width="1810" height="1354" />
        		  <img src="https://s3-us-west-2.amazonaws.com/safe-scenarios/Planet/monitoring/RGB/@Value(_rootname).png" rel="after"  width="1810" height="1354" />
        	   </div>
              </div>
           </div>
         </body>
        </html>
    -> HTML (writer HTML_1)
Note: Save (or stream) as HTML
HTML (writer HTML_1)
    attributes: html_content buffer
